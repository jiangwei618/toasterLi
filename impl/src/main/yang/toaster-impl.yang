module toaster-impl {
    yang-version 1;
    namespace "urn:opendaylight:params:xml:ns:yang:toaster:impl";
    prefix "toaster-impl";

    import config { prefix config; revision-date 2013-04-05; }
    import opendaylight-md-sal-binding { prefix mdsal; revision-date 2013-10-28; }

    description
        "Service definition for toaster project";

    revision "2014-12-10" {
        description
            "Initial revision";
    }

    identity toaster {
        base config:module-type;
        config:java-name-prefix Toaster;
    }

    augment "/config:modules/config:module/config:configuration" {
        case toaster {
            when "/config:modules/config:module/config:type = 'toaster'";
            container broker {
                uses config:service-ref {
                    refine type {
                        mandatory true;
                        //?????????mdsal???import????prefix????
                        config:required-identity mdsal:binding-broker-osgi-registry;
                    }
                }
            }

            //wires in the data-broker service
            container data-broker {
                uses config:service-ref {
                    refine type {
                        mandatory false;
                        config:required-identity mdsal:binding-async-data-broker;
                    }
                }
            }

            //Wires dependent services into this class - in this case the RPC registry service
             container rpc-registry {
                 uses config:service-ref {
                     refine type {
                         mandatory true;
                         config:required-identity mdsal:binding-rpc-registry;
                     }
                 }
             }
        }
    }
}
